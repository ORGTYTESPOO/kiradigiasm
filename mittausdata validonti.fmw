FME workspace mittausdata validonti.fmw

Parameters:
- SourceDataset_CAT = $(FME_MF_DIR)Tammitie.lis   # Source Column Aligned Text (CAT) File(s)
- SourceDataset_LANDXML = C:\Users\toomeve\Desktop\työ\Kira OH\201000_Ylin yhdistelmapinta_yyp_tammitie.xml   # Source LandXML File(s)

Readers:
- CAT_1: CAT from $(SourceDataset_CAT)
- LANDXML_1: LANDXML from $(SourceDataset_LANDXML)

CAT (reader CAT_1)
    attributes: Elementti int32, Nro int32, Koodi int32
    -> LineBuilder
LineBuilder
    ACCUM_INPUT_ATTRS = Use Attributes From One Feature
    BREAKATTR = Elementti
    LINE -> AreaBuilder
AreaBuilder
    SNAP_TOLERANCE = 0.1
    SNAPTYPE_PARAM = End Point Snapping
    LINES_AS_SEGMENTS = No
    CONSIDER_NODE_ELEVATION = no
    ALLOW_CYCLES = No
    DROP_HOLES = No
    CONNECT_Z_MODE = First Wins
    DONUT_CREATION = YES
    CHECK_CURVE_DIRECTION = No
    POLY_ACCUM_ATTRS_NAME = Use Attributes From One Feature
    AREA -> AreaBuilder_Area
    Incomplete -> AreaBuilder_Incomplete
    <REJECTED> -> AreaBuilder__Rejected_
AreaBuilder_Area: Inspector
AreaBuilder_Incomplete: Inspector
AreaBuilder__Rejected_: Inspector
Surface (reader LANDXML_1)
    attributes: Desc xml_char(21), Feature{}.Code xml_char(8), Feature{}.Property{}.Label xml_char(5), Feature{}.Property{}.Value xml_char(37), Name xml_char(32), State xml_char(9)
    -> Deaggregator
Deaggregator
    EXPLODE_INSTANCES = No
    MODE = Flatten All Levels
    GEOM_NAME_FIELD = _geometry_name
    SPLIT_COMPOSITES = No
    LIST_ATTR_MODE_LOOKUP = LEAN
    DEAGGREGATED -> Surface
Surface: Inspector
