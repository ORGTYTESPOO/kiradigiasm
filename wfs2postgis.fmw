FME workspace wfs2postgis.fmw

Parameters:
- SourceDataset_WFS =   # Source WFS (Web Feature Service) URL
- DestDataset_POSTGIS = awstesti   # Connection

Readers:
- WFS_1: WFS from $(SourceDataset_WFS)

Writers:
- POSTGIS_1: POSTGIS to $(DestDataset_POSTGIS)

InfStreet (reader WFS_1)
    attributes: gml_parent_id xml_buffer, gml_parent_property xml_buffer, gml_id xml_buffer, _TableName xml_buffer, ADDINFO1 xml_buffer, ADDINFO1TEXT xml_buffer, ADDINFO2 xml_buffer, ADDINFO2TEXT xml_buffer, ADMINISTRATIVECLASS xml_buffer, ADMINISTRATIVECLASSTEXT xml_buffer, AREA xml_real64, CALCULATEDAREA xml_real64, CALCULATEDLENGTH xml_real64, CLASSID xml_int32, COMPLETIONYEAR xml_int32, DRIVINGDIRECTION xml_int32, HEIGHTLIMIT xml_real64, ID xml_int32, LABEL xml_buffer, LENGTH xml_real64, MAINTAINEDBY xml_int32, MAINTAINEDBYTEXT xml_buffer, MAINTENANCECLASS xml_buffer, MAINTENANCECLASSTEXT xml_buffer, NAME xml_buffer, NOTETBID xml_int32, OWNER xml_int32, OWNERTEXT xml_buffer, PARTCLASS xml_int32, PARTCLASSTEXT xml_buffer,
      PARTLAYER xml_buffer, PARTNUMBER xml_int32, PAVINGCLASS xml_buffer, PAVINGCLASSTEXT xml_buffer, PAVINGNOTETBID xml_int32, POSSESSOR xml_int32, POSSESSORTEXT xml_buffer, REGISTERSTATE xml_int32, REGISTERSTATETEXT xml_buffer, REPAIRYEAR xml_int32, RPASTREETID xml_int32, SPEEDLIMIT xml_int32, SPEEDLIMITTEXT xml_buffer, STATUS xml_int32, STATUSTEXT xml_buffer, STREETDISTRICT xml_int32, STREETDISTRICTTEXT xml_buffer, TEXTREGISTERID xml_int32, USETYPE xml_int32, USETYPETEXT xml_buffer, WEIGHTLIMIT xml_real64, WINTERMAINTENANCE xml_int32, WINTERMAINTENANCEAREA xml_real64, WINTERMAINTENANCELENGTH xml_real64, WINTERMAINTENANCENOTETBID xml_int32, Geometry xml_geometry
    -> GeometryFilter
GeometryFilter
    GEOM_PORT_NAMES = Area
    BREAK_AGG = No
    AREA -> GeometryValidator
GeometryValidator
    CHECK_HOLE_TOUCHING_POLYGON = No
    CHECK_AREA_CHOICE = No
    OGC_VERSION_CHOICE = 1.2.0
    MISSING_TEXTURE_COORDINATES = MISSING_TEXTURE_COORDINATES
    ISSUE_ATTR_NAME = _issues
    REPAIR = Yes
    ANGULAR_TOLERANCE_CHOICE = Automatic
    SELF_INTERSECTING = SELF_INTERSECTING
    SHELL_VALIDATION = SHELL_VALIDATION
    TYPE_REPAIR = TYPE_REPAIR
    FLIP_APPEARANCES_CHOICE = Yes
    ORIENTATION_CHECK_DIR = Valid
    CONNECT_Z_MODE_SI = First Wins
    CONSECUTIVE_IDENTICAL_VERTICES_2D = CONSECUTIVE_IDENTICAL_VERTICES_2D
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    CONNECT_Z_MODE_TR = First Wins
    OGC_SIMPLE_CHECK = OGC_SIMPLE_CHECK
    DUP_COORDS_CHECK_Z = Yes
    SOLID_VOID_REPAIR = SOLID_VOID_REPAIR
    PLANAR_SURFACE = PLANAR_SURFACE
    SUMMARY = Detailed
    AREA_ORIENTATION = AREA_ORIENTATION
    ARC_ENDPOINT_TOLERANCE_MODE = Auto
    NULL_REMOVAL = NULL_REMOVAL
    OGC_VALID_CHECK = OGC_VALID_CHECK
    THICKNESS_TOLERANCE_CHOICE = Automatic
    NAN_REMOVAL = NAN_REMOVAL
    PRESETS = All
    MISSING_VERTEX_NORMALS = MISSING_VERTEX_NORMALS
    FAILED -> GeometryValidator_Failed
GeometryValidator_Failed: Inspector
katuindex (writer POSTGIS_1)
