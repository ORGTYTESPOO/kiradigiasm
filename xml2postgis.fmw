FME workspace xml2postgis.fmw

Parameters:
- SourceDataset_LANDXML = \\tyotilat.espoo.fi\DavWWWRoot\tyt\kake\muut_tyotilat\TiedonHallinta\Kiradigi omaisuudenhallinta\201000_Ylin yhdistelmapinta_yyp_tammitie.xml   # Source LandXML File(s)
- DestDataset_PDF2D = \\tyotilat.espoo.fi\DavWWWRoot\tyt\kake\muut_tyotilat\TiedonHallinta\Kiradigi omaisuudenhallinta\TietomallivirheetA3.pdf   # Destination Adobe Geospatial PDF File
- DestDataset_POSTGIS = aws_kiraoh   # Connection

Readers:
- LANDXML_1: LANDXML from $(SourceDataset_LANDXML)

Writers:
- PDF2D_1: PDF2D to $(DestDataset_PDF2D)
- POSTGIS_1: POSTGIS to $(DestDataset_POSTGIS) in EPSG:3879

Bookmark: XML source data (LandXML)
Surface (reader LANDXML_1)
    attributes: Desc xml_char(21), Feature{}.Code xml_char(8), Feature{}.Property{}.Label xml_char(5), Feature{}.Property{}.Value xml_char(37), Name xml_char(32), State xml_char(9)
    -> GeometryFilter

Bookmark: Filtering breaklines and extracting attributes
GeometryFilter
    BREAK_AGG = No
    GEOM_PORT_NAMES = Line Surface
    LINE -> Tester
    SURFACE -> 2DForcer
Tester
    TEST_CLAUSE = TEST @Evaluate(@NumCoords()) > 1
    BOOL_OP = OR
    TEST_MODE = Automatic
    TEST_DESCRIPTION = ""
    PASSED -> GeometryPropertyExtractor
GeometryPropertyExtractor
    EXTRACTTYPE_PARAM = Traits
    TRAIT_ATTR_LIST = Feature{0}.Property{1}.Value,No Name,No
    PREFIX_EXTRACTED_TRAITS = No
    EXTRACTED -> AttributeRenamer
AttributeRenamer
    ATTR_TABLE = RENAME_SET_DEFAULT Feature{0}.Property{1}.Value > breakline_type
    -> AttributeKeeper
Note: Breaklines to area and linetables
AttributeKeeper
    KEEP_ATTRS = breakline_type,Name
    -> PDFStyler
    -> Deaggregator
    -> AreaBuilder
PDFStyler
    LINE_JOIN_STYLE_PARAM = Miter Join
    FILL_COLOR = 0,0,0
    FONT = Arial
    LINE_CAP_STYLE_PARAM = Butt Cap
    OPACITY = 1.0
    LINE_DASH_PHASE = 0
    COLOR = FME_CONDITIONAL:DEFAULT_VALUE'0.854902,0.854902,0.854902'BOOL_OP;OR;COMPOSITE_TEST;<Unused>;TEST @Value(breakline_type) CONTAINS 122'1,0,0'BOOL_OP;OR;COMPOSITE_TEST;<Unused>;TEST @Value(breakline_type) CONTAINS 123'0,0,1'BOOL_OP;OR;COMPOSITE_TEST;<Unused>;TEST @Value(breakline_type) CONTAINS 141'1,0.666667,0'BOOL_OP;OR;COMPOSITE_TEST;<Unused>;TEST @Value(breakline_type) CONTAINS 140'0.666667,0,1'BOOL_OP;OR;COMPOSITE_TEST;<Unused>;TEST @Value(breakline_type) CONTAINS 131'0,1,1'BOOL_OP;OR;COMPOSITE_TEST;<Unused>;TEST @Value(breakline_type) CONTAINS 127'1,1,0'BOOL_OP;OR;COMPOSITE_TEST;<Unused>;TEST @Value(breakline_type) CONTAINS 124'0,1,0'FME_NUM_CONDITIONS8___
    LINE_MITER_LIMIT = 0.0
    FILL_OPACITY = 0.4
    LINE_WIDTH = FME_CONDITIONAL:DEFAULT_VALUE'1'BOOL_OP;OR;COMPOSITE_TEST;<Unused>;TEST @Value(breakline_type) CONTAINS 122;TEST @Value(breakline_type) CONTAINS 123;TEST @Value(breakline_type) CONTAINS 124'2'FME_NUM_CONDITIONS2___
    PDFStyled -> Layer1 (writer PDF2D_1)
Layer1 (writer PDF2D_1)

Bookmark: Surface to borderlines
2DForcer
    2D -> Deaggregator_2
Note: Surface to triangles
Deaggregator_2
    SPLIT_COMPOSITES = Yes
    LIST_ATTR_MODE_LOOKUP = LEAN
    EXPLODE_INSTANCES = No
    MODE = Flatten All Levels
    GEOM_NAME_FIELD = _geometry_name
    DEAGGREGATED -> GeometryFilter_2
GeometryFilter_2
    BREAK_AGG = No
    GEOM_PORT_NAMES = Line
    <UNFILTERED> -> Dissolver
Note: Joins triangles
Dissolver
    NO_OVRLP = No
    CONNECT_Z_MODE = First Wins
    ACCUM_INPUT_ATTRS = Get Attributes From One Representative Feature
    AREA -> GeometryCoercer
Note: Triangles to lines
GeometryCoercer
    KIND = fme_line
    GQUERY:
      for $geom in //geometry
      where $geom/count(parent::geometry) = 0
      return number($geom/@fme_id)
    COERCED -> AreaBuilder

Bookmark: Creating and inserting data to PostGIS
Deaggregator
    SPLIT_COMPOSITES = Yes
    LIST_ATTR_MODE_LOOKUP = LEAN
    EXPLODE_INSTANCES = No
    MODE = Flatten All Levels
    GEOM_NAME_FIELD = _geometry_name
    DEAGGREGATED -> AttributeSplitter
AttributeSplitter
    DROP_EMPTY_PARTS = No
    DELIMITER = " "
    TRIM_OPTION = Both
    ATTR_NAME = breakline_type
    LIST_NAME = codes_texts
    -> AttributeCreator
AttributeCreator
    ATTR_TABLE:
      SET_TO bktype = @Value(codes_texts{0})
      SET_TO bktext = @Value(codes_texts{1})
    -> oh.testline2 (writer POSTGIS_1)
oh.testline2 (writer POSTGIS_1) [off]
    attributes: bktype numeric(10,0), bktext varchar(254)
AreaBuilder
    CONSIDER_NODE_ELEVATION = no
    SNAPTYPE_PARAM = Vertex Snapping
    ALLOW_CYCLES = No
    POLY_ACCUM_ATTRS_NAME = Get Attributes From One Representative Feature
    SNAP_TOLERANCE = 0.1
    CHECK_CURVE_DIRECTION = No
    DONUT_CREATION = YES
    LINES_AS_SEGMENTS = No
    CONNECT_Z_MODE = First Wins
    DROP_HOLES = No
    AREA -> oh.testarea (writer POSTGIS_1)
    Incomplete -> AreaBuilder_Incomplete
oh.testarea (writer POSTGIS_1)
AreaBuilder_Incomplete: Inspector
oh.testgeom3d (writer POSTGIS_1)
    attributes: id numeric(20,0),PRIKEY, bktype numeric(10,0), bktext varchar(254)
