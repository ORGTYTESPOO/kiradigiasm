FME workspace InfraModel3_to_PostGIS.fmw
Title: InfraModel3 to PostGIS

Parameters:
- SourceDataset = \\tyotilat.espoo.fi\DavWWWRoot\tyt\kake\muut_tyotilat\TiedonHallinta\Kiradigi omaisuudenhallinta\201000_Ylin yhdistelmapinta_yyp_tammitie.xml   # Source LandXML File(s)
- ErrorReportPDF = \\tyotilat.espoo.fi\DavWWWRoot\tyt\kake\muut_tyotilat\TiedonHallinta\Kiradigi omaisuudenhallinta\TietomallivirheetA3_2017.pdf   # Error report PDF

Readers:
- LANDXML_1: LANDXML from $(SourceDataset)

Writers:
- PDF2D_1: PDF2D to $(ErrorReportPDF)
- POSTGIS_1: POSTGIS to aws_kiraoh in EPSG:3879

Bookmark: XML source data (LandXML)
Note: Attributes are stored in geometries as / geometry traits. https://docs.safe.com/fme/html/ / FME_Desktop_Documentation/FME_ReadersWriters/ / xml/geometry_traits_trait_element.htm
Note: Reads the Surface feature type from the source data
Surface (reader LANDXML_1)
    attributes: Desc xml_char(21), Feature{}.Code xml_char(8), Feature{}.Property{}.Label xml_char(5), Feature{}.Property{}.Value xml_char(37), Name xml_char(32), State xml_char(9)
    -> GeometryFilter

Bookmark: Filtering breaklines and extracting attributes from geometry traits
Note: Selects lines and surfaces from geometries. Other geometry types are filtered out.
GeometryFilter
    BREAK_AGG = No
    GEOM_PORT_NAMES = Line Surface
    LINE -> Tester
    SURFACE -> 2DForcer
Note: Tests if line has more than 1 coordinate (lines with just 1 coordinate are filtered out)
Tester
    TEST_DESCRIPTION = ""
    BOOL_OP = OR
    TEST_MODE = Automatic
    TEST_CLAUSE = TEST @Evaluate(@NumCoords()) > 1
    PASSED -> GeometryPropertyExtractor
Note: Extracts selected geometry traits to feature attributes. Geometry traits are attributes stored in geometries. / Feature{0}.Property{1}.Value, e.g / 122 paallysteen reuna / Name, e.g. 122_15
GeometryPropertyExtractor
    PREFIX_EXTRACTED_TRAITS = No
    TRAIT_ATTR_LIST = Feature{0}.Property{1}.Value,No Name,No
    EXTRACTTYPE_PARAM = Traits
    EXTRACTED -> AttributeRenamer
Note: Rename Feature{0}.Property{1}.Value to / breakline_type
AttributeRenamer
    ATTR_TABLE = RENAME_SET_DEFAULT Feature{0}.Property{1}.Value > breakline_type
    -> AttributeKeeper
Note: The transformer determines which / attributes are retained. / The other ones than breakline_type / and Name are removed.
Note: Breaklines
Note: Breaklines
Note: Triangle lines
AttributeKeeper
    KEEP_ATTRS = breakline_type,Name
    -> PDFStyler
    -> Deaggregator
    -> AreaBuilder
Note: Styles for error report. Different breakline_types are styled differently.
PDFStyler
    LINE_WIDTH = FME_CONDITIONAL:DEFAULT_VALUE'1'BOOL_OP;OR;COMPOSITE_TEST;<Unused>;TEST @Value(breakline_type) CONTAINS 122;TEST @Value(breakline_type) CONTAINS 123;TEST @Value(breakline_type) CONTAINS 124'2'FME_NUM_CONDITIONS2___
    FILL_COLOR = 0,0,0
    OPACITY = 1.0
    LINE_DASH_PHASE = 0
    COLOR = FME_CONDITIONAL:DEFAULT_VALUE'0.854902,0.854902,0.854902'BOOL_OP;OR;COMPOSITE_TEST;<Unused>;TEST @Value(breakline_type) CONTAINS 122'1,0,0'BOOL_OP;OR;COMPOSITE_TEST;<Unused>;TEST @Value(breakline_type) CONTAINS 123'0,0,1'BOOL_OP;OR;COMPOSITE_TEST;<Unused>;TEST @Value(breakline_type) CONTAINS 141'1,0.666667,0'BOOL_OP;OR;COMPOSITE_TEST;<Unused>;TEST @Value(breakline_type) CONTAINS 140'0.666667,0,1'BOOL_OP;OR;COMPOSITE_TEST;<Unused>;TEST @Value(breakline_type) CONTAINS 131'0,1,1'BOOL_OP;OR;COMPOSITE_TEST;<Unused>;TEST @Value(breakline_type) CONTAINS 127'1,1,0'BOOL_OP;OR;COMPOSITE_TEST;<Unused>;TEST @Value(breakline_type) CONTAINS 124'0,1,0'FME_NUM_CONDITIONS8___
    FONT = Arial
    LINE_CAP_STYLE_PARAM = Butt Cap
    FILL_OPACITY = 0.4
    LINE_MITER_LIMIT = 0.0
    LINE_JOIN_STYLE_PARAM = Miter Join
    PDFStyled -> Layer1 (writer PDF2D_1)

Bookmark: Surface to borderlines
Note: Flattens surfaces to 2D
2DForcer
    2D -> Deaggregator_2
Note: Decomposes surfaces to its components (triangles). / Surfaces in the source data are aggregates, which / consist triangles.
Deaggregator_2
    LIST_ATTR_MODE_LOOKUP = LEAN
    MODE = Flatten All Levels
    SPLIT_COMPOSITES = Yes
    GEOM_NAME_FIELD = _geometry_name
    EXPLODE_INSTANCES = No
    DEAGGREGATED -> GeometryFilter_2
Note: Filters out Lines from the geometries
GeometryFilter_2
    BREAK_AGG = No
    GEOM_PORT_NAMES = Line
    <UNFILTERED> -> Dissolver
Note: Joins triangles to / bigger areas
Dissolver
    DEAGGREGATE_INPUT = Yes
    CONNECT_Z_MODE = First Wins
    NO_OVRLP = No
    ACCUM_INPUT_ATTRS = Get Attributes From One Representative Feature
    AREA -> GeometryCoercer
Note: Resets the geometry type of the feature. / Here triangles are converted to lines.
GeometryCoercer
    GQUERY:
      for $geom in //geometry
      where $geom/count(parent::geometry) = 0
      return number($geom/@fme_id)
    KIND = fme_line
    COERCED -> AreaBuilder

Bookmark: Creating and inserting data to PostGIS
Note: Converts multigeometries to / separate geometries
Deaggregator
    LIST_ATTR_MODE_LOOKUP = LEAN
    MODE = Flatten All Levels
    SPLIT_COMPOSITES = Yes
    GEOM_NAME_FIELD = _geometry_name
    EXPLODE_INSTANCES = No
    DEAGGREGATED -> AttributeCreator
Note: Adds attributes bktype and bktext to the features, and gives values to them from breakline_type
AttributeCreator
    ATTR_TABLE:
      SET_TO bktype = @Value(breakline_type)
      SET_TO bktext = @Value(breakline_type)
    -> StringReplacer
Note: Extracts first digits from bktype / E.g. 122 paallysteen reuna -> 122
StringReplacer
    FIND_TEXT = [^\d]
    CASE = NO
    NO_MATCH = _FME_NO_OP_
    SRC_ATTRS = bktype
    REGEXP = YES
    -> StringReplacer_2
Note: Extracts everything else but / first digits and space from bktext / E.g. 122 paallysteen reuna -> paallysteen reuna
StringReplacer_2
    FIND_TEXT = "^\\d* "
    CASE = NO
    NO_MATCH = _FME_NO_OP_
    SRC_ATTRS = bktext
    REGEXP = YES
    -> testline2 (writer POSTGIS_1)
Note: Creates topologically correct polygon features from breaklines and triangle lines, where the lines form closed shapes. / Snapping tolerance is 0.1m.
AreaBuilder
    CHECK_CURVE_DIRECTION = No
    SNAP_TOLERANCE = 0.1
    CONNECT_Z_MODE = First Wins
    DONUT_CREATION = YES
    LINES_AS_SEGMENTS = No
    DROP_HOLES = No
    CONSIDER_NODE_ELEVATION = no
    ALLOW_CYCLES = No
    SNAPTYPE_PARAM = Vertex Snapping
    POLY_ACCUM_ATTRS_NAME = Get Attributes From One Representative Feature
    AREA -> testarea (writer POSTGIS_1)

Bookmark: PostGIS Writing (aws_kiraoh)
Note: Lines to oh.testline2
testline2 (writer POSTGIS_1)
    attributes: bktype numeric(10,0), bktext varchar(254)
Note: Areas to oh.testarea
testarea (writer POSTGIS_1)
testgeom3d (writer POSTGIS_1)
    attributes: id numeric(20,0),PRIKEY, bktype numeric(10,0), bktext varchar(254)

Bookmark: PDF Error Report
Note: Error report contains breaklines. Writes features to different PDF layers using brealine_type values.
Layer1 (writer PDF2D_1)

Bookmark: Usage notes
Note: This workspace writes lines and areas / from source Inframodel3 dataset. / Parameters: / SourceDataset (Source LandXML File(s):) / Source InfraModel3 dataset / ErrorReportPDF (Error report PDF:) / Error report PDF / Attributes in source dataset are stored in breaklines but not in surfaces.
